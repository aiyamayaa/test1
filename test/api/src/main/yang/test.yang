module test {
    yang-version 1;
    namespace "urn:opendaylight:params:xml:ns:yang:test";
    prefix "test";

    revision "2015-01-05" {
        description "Initial revision of test model";
    }
    rpc configtest{
        input{
            leaf config{
                type string;
            }
        }
        output{
            leaf greeting{
                type string;
            }

        }
    }
}
